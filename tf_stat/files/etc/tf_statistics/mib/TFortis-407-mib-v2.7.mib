FORT-TELECOM-MIB DEFINITIONS ::= BEGIN

    IMPORTS    
   		MODULE-IDENTITY, 
		OBJECT-TYPE, 
		OBJECT-IDENTITY,
		NOTIFICATION-TYPE, 
		enterprises 			FROM SNMPv2-SMI;     	
									   				   
               
			   
    forttelecomMIB MODULE-IDENTITY
                    
        LAST-UPDATED    "202008260000Z"  -- Aug 26, 2020
		
        ORGANIZATION "Fort-Telecom Ltd."

        CONTACT-INFO   "
			Editor: Belyaev Alexandr
			Fort-Telecom Ltd.
			Tel:    8-800-100-112-8
			E-mail: abelyaev@fort-telecom.ru
        "

       DESCRIPTION
             "The MIB module for managing TFortis switch.
            Copyright (c) Fort-Telecom (2020)."
			
      REVISION     "202008260000Z"  -- Aug 26, 2020
      DESCRIPTION "Fort-Telecom MIB"
	  
      ::= { enterprises 42019 }
		
	switch					OBJECT IDENTIFIER ::= { forttelecomMIB 3 }
	integrations			OBJECT IDENTIFIER ::= { forttelecomMIB 4 }
    psw					  	OBJECT IDENTIFIER ::= { switch 2}
	teleport				OBJECT IDENTIFIER ::= { integrations 2}
	
	--   TRAPS Group
	trapsPSW				OBJECT IDENTIFIER ::= { psw 0}
	trapsTLP				OBJECT IDENTIFIER ::= { teleport 0}
	
	--   SET Group
	configPSW				OBJECT IDENTIFIER ::= { psw 1}
	
	
	--   STATUS Group
	statusPSW				OBJECT IDENTIFIER ::= { psw 2}
	

		
	-- Set/Config Groups for Switches	
		--   Comfort Start set Group   
    	comfortStart			OBJECT IDENTIFIER ::= { configPSW 1}

		comfortStartTime	 OBJECT-TYPE
			SYNTAX      INTEGER (1..2)
			MAX-ACCESS  read-write
			STATUS      current
			DESCRIPTION
					"Comfort Start Time (in Hours)"
			::= { comfortStart 1 }
		
		comfStartTable OBJECT-TYPE
			SYNTAX     SEQUENCE OF ComfStartEntry
			MAX-ACCESS not-accessible
			STATUS     current
			DESCRIPTION
					""
			::= { comfortStart 2 }
			
		comfStartEntry OBJECT-TYPE
			SYNTAX     ComfStartEntry
			MAX-ACCESS not-accessible
			STATUS     current
			DESCRIPTION
					"An entry (conceptual row) in the comfStartTable."
			INDEX      { comfStIndex }
			::= { comfStartTable 1 }     
			
		ComfStartEntry ::= SEQUENCE {
			comfStIndex    INTEGER,
			comfStState    INTEGER
		} 

		
		comfStIndex OBJECT-TYPE
			SYNTAX     INTEGER
			MAX-ACCESS read-write
			STATUS     current
			DESCRIPTION
					""
			::= { comfStartEntry 1 }
			
		comfStState OBJECT-TYPE
			SYNTAX     INTEGER { enabled(1), disabled(2) }
			MAX-ACCESS read-write
			STATUS     current
			DESCRIPTION
					""
			::= { comfStartEntry 2 }
		
		
		--   Auto ReStart set Group
		autoRestart		OBJECT IDENTIFIER ::= { configPSW 2}

		autoRestartTable OBJECT-TYPE
			SYNTAX     SEQUENCE OF AutoRestartEntry
			MAX-ACCESS not-accessible
			STATUS     current
			DESCRIPTION
					""
			::= { autoRestart 1 }
			
		autoRestartEntry OBJECT-TYPE
			SYNTAX     AutoRestartEntry
			MAX-ACCESS not-accessible
			STATUS     current
			DESCRIPTION
					"An entry (conceptual row) in the autoRestartTable."
			INDEX      { autoRstIndex }
			::= { autoRestartTable 1 }
			
		AutoRestartEntry ::= SEQUENCE {
			autoRstIndex    INTEGER,
			autoRstMode     INTEGER,
			autoRstDstIP    IpAddress,
			autoRstSpeedDown INTEGER,
			autoRstSpeedUp   INTEGER
		}
		
		autoRstIndex OBJECT-TYPE
			SYNTAX     INTEGER 
			MAX-ACCESS read-write
			STATUS     current
			DESCRIPTION
					""
			::= { autoRestartEntry 1 }
			
		autoRstMode OBJECT-TYPE
			SYNTAX     INTEGER { link(1),ping(2),speed(3),time(4),disabled(0) }
			MAX-ACCESS read-write
			STATUS     current
			DESCRIPTION
					"Mode of Auto Restart controller"
			::= { autoRestartEntry 2 }
			
		autoRstDstIP OBJECT-TYPE
			SYNTAX     IpAddress 
			MAX-ACCESS read-write
			STATUS     current
			DESCRIPTION
					"IP address of device"
			::= { autoRestartEntry 3 }
		
		autoRstSpeedDown OBJECT-TYPE
			SYNTAX     INTEGER 
			MAX-ACCESS read-write
			STATUS     current
			DESCRIPTION
					"Lower level of speed"
			::= { autoRestartEntry 4 }
			
		autoRstSpeedUp OBJECT-TYPE
			SYNTAX     INTEGER 
			MAX-ACCESS read-write
			STATUS     current
			DESCRIPTION
					"Upper level of speed"
			::= { autoRestartEntry 5 }
			
		autoReStartTimeOnHour OBJECT-TYPE
			SYNTAX     INTEGER 
			MAX-ACCESS read-write
			STATUS     current
			DESCRIPTION
					"Hour of PoE Enable"
			::= { autoRestartEntry 6 }
			
		autoReStartTimeOnMin OBJECT-TYPE
			SYNTAX     INTEGER 
			MAX-ACCESS read-write
			STATUS     current
			DESCRIPTION
					"Minute of PoE Enable"
			::= { autoRestartEntry 7 }
			
		autoReStartTimeOffHour OBJECT-TYPE
			SYNTAX     INTEGER 
			MAX-ACCESS read-write
			STATUS     current
			DESCRIPTION
					"Hour of PoE Disable"
			::= { autoRestartEntry 8 }
			
		autoReStartTimeOffMin OBJECT-TYPE
			SYNTAX     INTEGER 
			MAX-ACCESS read-write
			STATUS     current
			DESCRIPTION
					"Minute of PoE Disable"
			::= { autoRestartEntry 9 }
			
		--   PoE set Group   
    	portPoe			OBJECT IDENTIFIER ::= { configPSW 3}
	
		portPoeTable OBJECT-TYPE
			SYNTAX     SEQUENCE OF PortPoeEntry
			MAX-ACCESS not-accessible
			STATUS     current
			DESCRIPTION
					""
			::= { portPoe 1 }
			
		portPoeEntry OBJECT-TYPE
			SYNTAX     PortPoeEntry
			MAX-ACCESS not-accessible
			STATUS     current
			DESCRIPTION
					"An entry (conceptual row) in the portPoeTable."
			INDEX      { portPoeIndex }
			::= { portPoeTable 1 }     
			
		PortPoeEntry ::= SEQUENCE {
			portPoeIndex    INTEGER,
			portPoeState    INTEGER
		} 

		
		portPoeIndex OBJECT-TYPE
			SYNTAX     INTEGER
			MAX-ACCESS read-write
			STATUS     current
			DESCRIPTION
					"Port Number"
			::= { portPoeEntry 1 }
			
		portPoeState OBJECT-TYPE
			SYNTAX     INTEGER { enabled(1), disabled(2) }
			MAX-ACCESS read-write
			STATUS     current
			DESCRIPTION
					"PoE State"
			::= { portPoeEntry 2 }
		
		
		
		-- Output Relay State
		outStatePSW	OBJECT IDENTIFIER ::= { configPSW 4}
		
		state OBJECT-TYPE
			SYNTAX     INTEGER { open(1), short(2) }
			MAX-ACCESS read-write
			STATUS     current
			DESCRIPTION
					"Output Relay State"
			::= { outStatePSW 1 }
		
		-- Traps group for Switches		

		stpTopologyChanged		NOTIFICATION-TYPE
			STATUS		current
			DESCRIPTION "STP Topology changed events occur"
			::= { trapsPSW 1}
			
	
			
		specialFunctionNoLink				NOTIFICATION-TYPE
			STATUS      current
			DESCRIPTION
				" This Notification indicates no link activity at activated 
				SpecialFunctions by criterion a link"
			::= { trapsPSW 2}
			 
		specialFunctionNoPingResponse		NOTIFICATION-TYPE
			STATUS      current
			DESCRIPTION
				" This Notification indicates no ping response at activated 
				SpecialFunctions by criterion a ping"
			::= { trapsPSW 3}
		
		specialFunctionLowSpeed			NOTIFICATION-TYPE
			STATUS      current
			DESCRIPTION
				"This Notification indicates low speed on port at activated 
				SpecialFunctions by criterion a speed"
			::= { trapsPSW 4}
		

	
		updateFirmware			NOTIFICATION-TYPE
			STATUS      current
			DESCRIPTION
				" This Notification indicates a firmwre updating"
			::= { trapsPSW 5}

		
		setToDefault			NOTIFICATION-TYPE
			STATUS      current
			DESCRIPTION
				"Settings to default"
			::= { trapsPSW 6}

		
		backupSettings				NOTIFICATION-TYPE
			STATUS      current
			DESCRIPTION
				"Make backup copy of settings in file"
			::= { trapsPSW 7}
			
			
		systemWarmStart				NOTIFICATION-TYPE
			STATUS      current
			DESCRIPTION
				"Start system after reboot"
			::= { trapsPSW 8}
			
		systemColdStart				NOTIFICATION-TYPE
			STATUS      current
			DESCRIPTION
				"Start system after power down (Cold start)"
			::= { trapsPSW 9}
		
		webInterfaceLoginOk			NOTIFICATION-TYPE
			STATUS      current
			DESCRIPTION
				"Successfully authentification on web-interface"
			::= { trapsPSW 10}
			
		webInterfaceLoginFail			NOTIFICATION-TYPE
			STATUS      current
			DESCRIPTION
				"Fail authentification on web-interface"
			::= { trapsPSW 11}
			
		emptyArpTable			NOTIFICATION-TYPE
			STATUS      current
			DESCRIPTION
				"Arp table is empty"
			::= { trapsPSW 12}
		
			
				
		upsLowVoltage				NOTIFICATION-TYPE
			STATUS      current
			DESCRIPTION
				"UPS: Voltage on battery is low (below than 44V)"
			::= { trapsPSW 13}
			
		upsBattrtyPower			NOTIFICATION-TYPE
			STATUS      current
			DESCRIPTION
				"UPS: Power souce is battery"
			::= { trapsPSW 14}
			
		upsVacPower			NOTIFICATION-TYPE
			STATUS      current
			DESCRIPTION
				"UPS: Power souce is external VAC"
			::= { trapsPSW 15}
		
		
		
		--asc group (SKUD)
		tamperIsActive			NOTIFICATION-TYPE
			STATUS      current
			DESCRIPTION
				"Sensor 0 (Tamper) is active."
			::= { trapsPSW 16}
			
		sensor1isActive			NOTIFICATION-TYPE
			STATUS      current
			DESCRIPTION
				"Sensor 1 (dry contact) is active"
			::= { trapsPSW 17}
			
		sensor2isActive			NOTIFICATION-TYPE
			STATUS      current
			DESCRIPTION
				"Sensor 2 (dry contact) is active"
			::= { trapsPSW 18}

		input1isActive			NOTIFICATION-TYPE
			STATUS      current
			DESCRIPTION
				"Input 1 is active"
			::= { trapsPSW 19}
			
		input2isActive			NOTIFICATION-TYPE
			STATUS      current
			DESCRIPTION
				"Input 2 is active"
			::= { trapsPSW 20}	
			
		input3isActive			NOTIFICATION-TYPE
			STATUS      current
			DESCRIPTION
				"Input 3 is active"
			::= { trapsPSW 21}
			
		input4isActive			NOTIFICATION-TYPE
			STATUS      current
			DESCRIPTION
				"Input 4 is active"
			::= { trapsPSW 22}	
			
				
		
		macFilteringAlarm		NOTIFICATION-TYPE
			STATUS      current
			DESCRIPTION
				"Unallowed MAC address: "
			::= { trapsPSW 23}
			
		portErrorDisabled		NOTIFICATION-TYPE
			STATUS      current
			DESCRIPTION
				"Port Error-Disabled"
			::= { trapsPSW 24}
				
		pwr180DiagnosticError		NOTIFICATION-TYPE
			STATUS      current
			DESCRIPTION
				"The error of the PWR-180 power supply was diagnosed, check the power supply"
			::= { trapsPSW 25}
			
			
		temperatureSensorLow		NOTIFICATION-TYPE
			STATUS      current
			DESCRIPTION		"Temperature: low level"				
			::= { trapsPSW 26}
			
		temperatureSensorHigh		NOTIFICATION-TYPE
			STATUS      current
			DESCRIPTION	"Temperature: high level"
			::= { trapsPSW 27}
			
		humiditySensorLow		NOTIFICATION-TYPE
			STATUS      current
			DESCRIPTION		"Humidity: low level"				
			::= { trapsPSW 28}
			
		humiditySensorHigh		NOTIFICATION-TYPE
			STATUS      current
			DESCRIPTION
				"Humidity: high level"
			::= { trapsPSW 29}
			
		leakageSensorAlarm		NOTIFICATION-TYPE
			STATUS      current
			DESCRIPTION
				"Leakage sensor is active: 1 - Normal, 2 - Alarm"
			::= { trapsPSW 30}
				
			
	-- Status group for Switches
		-- UPS status group
		upsStatus			OBJECT IDENTIFIER ::= { statusPSW 1}

		upsModeAvalible	 OBJECT-TYPE
			SYNTAX     INTEGER { true(1), false(2) }
			MAX-ACCESS  read-only
			STATUS      current
			DESCRIPTION
					"UPS option is avalible. 'true' for switches with UPS module."
			::= { upsStatus 1 }
			
		upsPwrSource   OBJECT-TYPE
			SYNTAX     INTEGER { battery(1), ac(2) }
			MAX-ACCESS  read-only
			STATUS      current
			DESCRIPTION
					"This variable  shows the power source for switch. 'Battery' - power source is battery,
					no external AC voltage. 'AC' - power source is external AC voltage,normal operation.
					This option only for switches with UPS module."
			::= { upsStatus 2 }
			
		upsBatteryVoltage   OBJECT-TYPE
			SYNTAX      INTEGER 
			MAX-ACCESS  read-only
			STATUS      current
			DESCRIPTION
					"This variable shows battery voltage. This option only for switches with UPS module."
			::= { upsStatus 3 }
			
		upsBatteryTime   OBJECT-TYPE
			SYNTAX      INTEGER 
			MAX-ACCESS  read-only
			STATUS      current
			DESCRIPTION
					"This variable shows estimated operating time (in sec.) of the device after switching to battery power (only for devices with UPS module)."
			::= { upsStatus 4 }
			
		-- Inputs status group
		inputStatus			OBJECT IDENTIFIER ::= { statusPSW 2}	
		
		inputStatusTable OBJECT-TYPE
			SYNTAX     SEQUENCE OF InputStatusEntry
			MAX-ACCESS not-accessible
			STATUS     current
			DESCRIPTION
					""
			::= { inputStatus 1 }
			
		inputStatusEntry OBJECT-TYPE
			SYNTAX     InputStatusEntry
			MAX-ACCESS not-accessible
			STATUS     current
			DESCRIPTION
					"An entry (conceptual row) in the portPoeTable."
			INDEX      { inputIndex }
			::= { inputStatusTable 1 }     
			
		InputStatusEntry ::= SEQUENCE {
			inputIndex    INTEGER,
			inputType     INTEGER,
			inputState    INTEGER,
			inputAlarm    INTEGER
		} 

		
		inputIndex OBJECT-TYPE
			SYNTAX     INTEGER
			MAX-ACCESS read-write
			STATUS     current
			DESCRIPTION
					"Input Number"
			::= { inputStatusEntry 1 }
			
		inputType OBJECT-TYPE
			SYNTAX     INTEGER{ build-in(1), plc(2) }
			MAX-ACCESS read-only
			STATUS     current
			DESCRIPTION
					"Input Type: 'buil-in' - inputs on main board, 'plc' - inputs on optional board"
			::= { inputStatusEntry 2 }
			
		inputState OBJECT-TYPE
			SYNTAX     INTEGER{ short(1), open(2) }
			MAX-ACCESS read-only
			STATUS     current
			DESCRIPTION
					"Input State"
			::= { inputStatusEntry 3 }
			
		inputAlarm OBJECT-TYPE
			SYNTAX     INTEGER{ short(1), open(2), any(3) }
			MAX-ACCESS read-only
			STATUS     current
			DESCRIPTION
					"Alarm state condition"
			::= { inputStatusEntry 4 }
		
		-- Firmware status group
		fwStatus	OBJECT IDENTIFIER ::= { statusPSW 3}	
		
		fwVersion OBJECT-TYPE
			SYNTAX     OCTET STRING
			MAX-ACCESS read-only
			STATUS     current
			DESCRIPTION
					"Firmware version"
			::= { fwStatus 1 }
			
			
		-- PoE status group	
		PoeStatusEntry ::= SEQUENCE {
			portPoeStatusIndex    INTEGER,
			portPoeStatusState  	INTEGER,
			portPoeStatusPower	INTEGER
		} 
		
		poeStatus		OBJECT IDENTIFIER ::= { statusPSW 5}
	
		poeStatusTable OBJECT-TYPE
			SYNTAX     SEQUENCE OF PoeStatusEntry
			MAX-ACCESS not-accessible
			STATUS     current
			DESCRIPTION
					""
			::= { poeStatus 1 }
			
		poeStatusEntry OBJECT-TYPE
			SYNTAX     PoeStatusEntry
			MAX-ACCESS not-accessible
			STATUS     current
			DESCRIPTION
					"An entry (conceptual row) in the portPoeTable."
			INDEX      { portPoeStatusIndex }
			::= { poeStatusTable 1 }     
			


		
		portPoeStatusIndex OBJECT-TYPE
			SYNTAX     INTEGER
			MAX-ACCESS read-write
			STATUS     current
			DESCRIPTION
					"Port Number"
			::= { poeStatusEntry 1 }
			
		portPoeStatusState OBJECT-TYPE
			SYNTAX     INTEGER { up(1), down(2) }
			MAX-ACCESS read-only
			STATUS     current
			DESCRIPTION
					"PoE State"
			::= { poeStatusEntry 2 }
			
		portPoeStatusPower OBJECT-TYPE
			SYNTAX     INTEGER
			MAX-ACCESS read-only
			STATUS     current
			DESCRIPTION
					"PoE load power (in mW) "
			::= { poeStatusEntry 3 }
			
		-- Special Funtion status group	
		specialStatus		OBJECT IDENTIFIER ::= { statusPSW 6}	
			
			-- Auto Restart Errors
			AutoRestartErrorsEntry ::= SEQUENCE {
				arPortIndex     INTEGER,
				arPortStatus    INTEGER
			} 

			autoRestartErrors OBJECT IDENTIFIER ::= { specialStatus 1}
			
				autoRestartErrorsTable OBJECT-TYPE
					SYNTAX     SEQUENCE OF AutoRestartErrorsEntry
					MAX-ACCESS not-accessible
					STATUS     current
					DESCRIPTION
					""
					::= { autoRestartErrors 1 }
			
			 		 
			
				autoRestartErrorsEntry OBJECT-TYPE
					SYNTAX     AutoRestartErrorsEntry
					MAX-ACCESS not-accessible
					STATUS     current
					DESCRIPTION
							"An entry (conceptual row) in the autoRestartErrorsTable."
					INDEX      { arPortIndex }
					::= { autoRestartErrorsTable 1 }     
			

		
				arPortIndex OBJECT-TYPE
					SYNTAX     INTEGER
					MAX-ACCESS read-write
					STATUS     current
					DESCRIPTION
							"Port Number"
					::= { autoRestartErrorsEntry 1 }
			
				arPortStatus OBJECT-TYPE
					SYNTAX     INTEGER { normal(1), noLink(2), noPing(3), lowSpeed(4) }
					MAX-ACCESS read-only
					STATUS     current
					DESCRIPTION
							"State of special function 'AutoRestart'. 
							'normal' - no error, 
							'noLink' - no link activity on port,
							'noPing' - no answer to ping,
							'lowSpeed' - low speed on port"
					::= { autoRestartErrorsEntry 2 }
			
			
			-- Comfort start Status
			comfortStartStatus OBJECT IDENTIFIER ::= { specialStatus 2}
			
				comfortStartStatusTable OBJECT-TYPE
					SYNTAX     SEQUENCE OF ComfortStartStatusEntry
					MAX-ACCESS not-accessible
					STATUS     current
					DESCRIPTION
					""
					::= { comfortStartStatus 1 }
			
			 		 
			
				comfortStartStatusEntry OBJECT-TYPE
					SYNTAX     ComfortStartStatusEntry
					MAX-ACCESS not-accessible
					STATUS     current
					DESCRIPTION
							"An entry (conceptual row) in the comfortStartStatusTable."
					INDEX      { csPortIndex }
					::= { comfortStartStatusTable 1 }     
			
				ComfortStartStatusEntry ::= SEQUENCE {
					csPortIndex     INTEGER,
					csPortStatus    INTEGER
				} 

		
				csPortIndex OBJECT-TYPE
					SYNTAX     INTEGER
					MAX-ACCESS read-write
					STATUS     current
					DESCRIPTION
							"Port Number"
					::= { comfortStartStatusEntry 1 }
			
				csPortStatus OBJECT-TYPE
					SYNTAX     INTEGER { normal(1), processing(2) }
					MAX-ACCESS read-only
					STATUS     current
					DESCRIPTION
							"State of special function 'ComfortStart' on port. 
							'normal' - ComfortStart is ready, 
							'processing' - ComfortStart in processing"
					::= { comfortStartStatusEntry 2 }
					
					
		-- SFP modules status group	
		SfpStatusEntry ::= SEQUENCE {
			portSfpIndex  INTEGER,
			portSfpPresent  INTEGER,
			portSfpSignalDetect  INTEGER,
			portSfpVendor		OCTET STRING,
			portSfpOui			OCTET STRING,
			portSfpPartNumber	OCTET STRING,
			portSfpRevision		OCTET STRING,
			portSfpTemperature	INTEGER,
			portSfpVoltage		INTEGER,
			portSfpBiasCurrent	INTEGER,
			portSfpTxOutPower	INTEGER,
			portSfpTxOutPowerDb	INTEGER,
			portSfpRxOutPower	INTEGER,
			portSfpRxOutPowerDb	INTEGER			
		} 
		sfpStatus		OBJECT IDENTIFIER ::= { statusPSW 7}

		sfpStatusTable OBJECT-TYPE
			SYNTAX     SEQUENCE OF SfpStatusEntry
			MAX-ACCESS not-accessible
			STATUS     current
			DESCRIPTION
					""
			::= { sfpStatus 1 }
			
		sfpStatusEntry OBJECT-TYPE
			SYNTAX     SfpStatusEntry
			MAX-ACCESS not-accessible
			STATUS     current
			DESCRIPTION
					"An entry (conceptual row) in the sfpStatusTable."
			INDEX      { portSfpIndex }
			::= { sfpStatusTable 1 }     

		portSfpIndex OBJECT-TYPE
			SYNTAX     INTEGER
			MAX-ACCESS read-write
			STATUS     current
			DESCRIPTION
					"SFP port number"
			::= { sfpStatusEntry 1 }
			
		portSfpPresent OBJECT-TYPE
			SYNTAX     INTEGER 
			MAX-ACCESS read-only
			STATUS     current
			DESCRIPTION
					"Present of SFP module in the case"
			::= { sfpStatusEntry 2 }
			
		portSfpSignalDetect OBJECT-TYPE
			SYNTAX     INTEGER 
			MAX-ACCESS read-only
			STATUS     current
			DESCRIPTION
					"Optical Signal Detect of SFP module"
			::= { sfpStatusEntry 3 }
			
		portSfpVendor OBJECT-TYPE
			SYNTAX     DisplayString  ( SIZE ( 0 .. 255  ) )  
			MAX-ACCESS read-only
			STATUS     current
			DESCRIPTION
					"SFP module Vendor"
			::= { sfpStatusEntry 4 }
			
		portSfpOui OBJECT-TYPE
			SYNTAX     DisplayString  ( SIZE ( 0 .. 255  ) )  
			MAX-ACCESS read-only
			STATUS     current
			DESCRIPTION
					"SFP module Vendor OUI"
			::= { sfpStatusEntry 5 }
			
		portSfpPartNumber OBJECT-TYPE
			SYNTAX     DisplayString  ( SIZE ( 0 .. 255  ) )  
			MAX-ACCESS read-only
			STATUS     current
			DESCRIPTION
					"SFP module Part Number"
			::= { sfpStatusEntry 6 }
			
		portSfpRevision OBJECT-TYPE
			SYNTAX     DisplayString  ( SIZE ( 0 .. 255  ) )  
			MAX-ACCESS read-only
			STATUS     current
			DESCRIPTION
					"SFP module Revision"
			::= { sfpStatusEntry 7 }
			
		portSfpTemperature OBJECT-TYPE
			SYNTAX     INTEGER 
			MAX-ACCESS read-only
			STATUS     current
			DESCRIPTION
					"Temperature of SFP module. In degrees Celsius"
			::= { sfpStatusEntry 8 }
			
		portSfpVoltage OBJECT-TYPE
			SYNTAX     INTEGER 
			MAX-ACCESS read-only
			STATUS     current
			DESCRIPTION
					"Voltage in SFP module (mV)"
			::= { sfpStatusEntry 9 }
			
		portSfpBiasCurrent OBJECT-TYPE
			SYNTAX     INTEGER 
			MAX-ACCESS read-only
			STATUS     current
			DESCRIPTION
					"TX bias current (uA)"
			::= { sfpStatusEntry 10 }
			
		portSfpTxOutPower OBJECT-TYPE
			SYNTAX     INTEGER 
			MAX-ACCESS read-only
			STATUS     current
			DESCRIPTION
					"TX output optical power (uW)"
			::= { sfpStatusEntry 11 }
			
		portSfpTxOutPowerDb OBJECT-TYPE
			SYNTAX     INTEGER 
			MAX-ACCESS read-only
			STATUS     current
			DESCRIPTION
					"TX output optical power (dB)"
			::= { sfpStatusEntry 12 }
			
		portSfpRxOutPower OBJECT-TYPE
			SYNTAX     INTEGER 
			MAX-ACCESS read-only
			STATUS     current
			DESCRIPTION
					"RX output optical power (uW)"
			::= { sfpStatusEntry 13 }
			
		portSfpRxOutPowerDb OBJECT-TYPE
			SYNTAX     INTEGER 
			MAX-ACCESS read-only
			STATUS     current
			DESCRIPTION
					"RX output optical power (dB)"
			::= { sfpStatusEntry 14 }
			
		
		-- Temperature/Humidity sensor group	
		SensorEntry ::= SEQUENCE {			
			sensorConnected  INTEGER,
			sensorTemperature	INTEGER,
			sensorHumidity	INTEGER,		
			sensorTemperatureMin INTEGER,
			sensorTemperatureMax INTEGER				
		} 
		sensorEntry		OBJECT IDENTIFIER ::= { statusPSW 8}
		sensorConnected OBJECT-TYPE
			SYNTAX     INTEGER { connected(1), disconnected(2) }
			MAX-ACCESS read-only
			STATUS     current
			DESCRIPTION		"Connection status of temperature/humidity sensor"
			::= { sensorEntry 1 }
			
		sensorTemperature OBJECT-TYPE
			SYNTAX     INTEGER 
			MAX-ACCESS read-only
			STATUS     current
			DESCRIPTION		"Temperature value"
			::= { sensorEntry 2 }
			
		sensorHumidity OBJECT-TYPE
			SYNTAX     INTEGER 
			MAX-ACCESS read-only
			STATUS     current
			DESCRIPTION		"Humidity value"
			::= { sensorEntry 3 }
			
		sensorTemperatureMin OBJECT-TYPE
			SYNTAX     INTEGER 
			MAX-ACCESS read-write
			STATUS     current
			DESCRIPTION		"Minimal value of temperature"
			::= { sensorEntry 4 }
			
		sensorTemperatureMax OBJECT-TYPE
			SYNTAX     INTEGER 
			MAX-ACCESS read-write
			STATUS     current
			DESCRIPTION		"Maximal value of temperature"
			::= { sensorEntry 5 }
			
		sensorHumidityMin OBJECT-TYPE
			SYNTAX     INTEGER 
			MAX-ACCESS read-write
			STATUS     current
			DESCRIPTION		"Minimal value of Humidity"
			::= { sensorEntry 6 }
			
		sensorHumidityMax OBJECT-TYPE
			SYNTAX     INTEGER 
			MAX-ACCESS read-write
			STATUS     current
			DESCRIPTION		"Maximal value of Humidity"
			::= { sensorEntry 7 }
		
		
-- Parts for Teleport					
		-- Set/Config Groups	
		-- Traps group		
		updateFirmwareTLP			NOTIFICATION-TYPE
			STATUS      current
			DESCRIPTION
				" This Notification indicates a firmwre updating"
			::= { trapsTLP 1}

		
		setToDefaultTLP			NOTIFICATION-TYPE
			STATUS      current
			DESCRIPTION
				"Settings to default"
			::= { trapsTLP 2}

		
		backupSettingsTLP				NOTIFICATION-TYPE
			STATUS      current
			DESCRIPTION
				"Make backup copy of settings in file"
			::= { trapsTLP 3}
			
			
		systemWarmStartTLP				NOTIFICATION-TYPE
			STATUS      current
			DESCRIPTION
				"Start system after reboot"
			::= { trapsTLP 4}
			
		systemColdStartTLP			NOTIFICATION-TYPE
			STATUS      current
			DESCRIPTION
				"Start system after power down (Cold start)"
			::= { trapsTLP 5}
		
		webInterfaceLoginOkTLP			NOTIFICATION-TYPE
			STATUS      current
			DESCRIPTION
				"Successfully authentification on web-interface"
			::= { trapsTLP 6}
			
		webInterfaceLoginFailTLP			NOTIFICATION-TYPE
			STATUS      current
			DESCRIPTION
				"Fail authentification on web-interface"
			::= { trapsTLP 7}
			
		emptyArpTableTLP			NOTIFICATION-TYPE
			STATUS      current
			DESCRIPTION
				"Arp table is empty"
			::= { trapsTLP 8}
		
		
			
		input1isChanged			NOTIFICATION-TYPE
			STATUS      current
			DESCRIPTION
				"Input 1 is changed"
			::= { trapsTLP 9}
			
		input2isChanged			NOTIFICATION-TYPE
			STATUS      current
			DESCRIPTION
				"Input 2 is changed"
			::= { trapsTLP 10}
			
		input3isChanged			NOTIFICATION-TYPE
			STATUS      current
			DESCRIPTION
				"Input 3 is changed"
			::= { trapsTLP 11}
			
		input4isChanged			NOTIFICATION-TYPE
			STATUS      current
			DESCRIPTION
				"Input 4 is changed"
			::= { trapsTLP 12}
			
		input5isChanged			NOTIFICATION-TYPE
			STATUS      current
			DESCRIPTION
				"Input 5 is changed"
			::= { trapsTLP 13}	

		input6isChanged			NOTIFICATION-TYPE
			STATUS      current
			DESCRIPTION
				"Input 6 is changed"
			::= { trapsTLP 14}

		input7isChanged			NOTIFICATION-TYPE
			STATUS      current
			DESCRIPTION
				"Input 7 is changed"
			::= { trapsTLP 15}			
				
		input8isChanged			NOTIFICATION-TYPE
			STATUS      current
			DESCRIPTION
				"Input 8 is changed"
			::= { trapsTLP 16}	

		input9isChanged			NOTIFICATION-TYPE
			STATUS      current
			DESCRIPTION
				"Input 9 is changed"
			::= { trapsTLP 17}			
		
		output1isChanged			NOTIFICATION-TYPE
			STATUS      current
			DESCRIPTION
				"Output 1 is changed"
			::= { trapsTLP 18}
			
		output2isChanged			NOTIFICATION-TYPE
			STATUS      current
			DESCRIPTION
				"Output 2 is changed"
			::= { trapsTLP 19}
			
		output3isChanged			NOTIFICATION-TYPE
			STATUS      current
			DESCRIPTION
				"Output 3 is changed"
			::= { trapsTLP 20}	
			
		output4isChanged			NOTIFICATION-TYPE
			STATUS      current
			DESCRIPTION
				"Output 4 is changed"
			::= { trapsTLP 21}
				
		output5isChanged			NOTIFICATION-TYPE
			STATUS      current
			DESCRIPTION
				"Output 5 is changed"
			::= { trapsTLP 22}
				
		output6isChanged			NOTIFICATION-TYPE
			STATUS      current
			DESCRIPTION
				"Output 6 is changed"
			::= { trapsTLP 23}
			
		output7isChanged			NOTIFICATION-TYPE
			STATUS      current
			DESCRIPTION
				"Output 7 is changed"
			::= { trapsTLP 24}
			
		output8isChanged			NOTIFICATION-TYPE
			STATUS      current
			DESCRIPTION
				"Output 8 is changed"
			::= { trapsTLP 25}
				
		output9isChanged			NOTIFICATION-TYPE
			STATUS      			current
			DESCRIPTION
				"Output 9 is changed"
			::= { trapsTLP 26}
			
		device1connFail				NOTIFICATION-TYPE
			STATUS      			current
			DESCRIPTION
				"Device 1 connection fail"
			::= { trapsTLP 27}
			
		device2connFail				NOTIFICATION-TYPE
			STATUS      			current
			DESCRIPTION
				"Device 2 connection fail"
			::= { trapsTLP 28}
			
		device3connFail				NOTIFICATION-TYPE
			STATUS      			current
			DESCRIPTION
				"Device 3 connection fail"
			::= { trapsTLP 29}
			
		device4connFail				NOTIFICATION-TYPE
			STATUS      			current
			DESCRIPTION
				"Device 4 connection fail"
			::= { trapsTLP 30}
			
		device5connFail				NOTIFICATION-TYPE
			STATUS      			current
			DESCRIPTION
				"Device 5 connection fail"
			::= { trapsTLP 31}
			
		device6connFail				NOTIFICATION-TYPE
			STATUS      			current
			DESCRIPTION
				"Device 6 connection fail"
			::= { trapsTLP 32}
			
		device7connFail				NOTIFICATION-TYPE
			STATUS      			current
			DESCRIPTION
				"Device 7 connection fail"
			::= { trapsTLP 33}
			
		device8connFail				NOTIFICATION-TYPE
			STATUS      			current
			DESCRIPTION
				"Device 8 connection fail"
			::= { trapsTLP 34}
			
		device9connFail				NOTIFICATION-TYPE
			STATUS      			current
			DESCRIPTION
				"Device 9 connection fail"
			::= { trapsTLP 35}

		device10connFail			NOTIFICATION-TYPE
			STATUS      			current
			DESCRIPTION
				"Device 10 connection fail"
			::= { trapsTLP 36}

		device11connFail			NOTIFICATION-TYPE
			STATUS      			current
			DESCRIPTION
				"Device 11 connection fail"
			::= { trapsTLP 37}
			
		device12connFail			NOTIFICATION-TYPE
			STATUS      			current
			DESCRIPTION
				"Device 12 connection fail"
			::= { trapsTLP 38}	

		device13connFail			NOTIFICATION-TYPE
			STATUS      			current
			DESCRIPTION
				"Device 13 connection fail"
			::= { trapsTLP 39}
			
		device14connFail			NOTIFICATION-TYPE
			STATUS      			current
			DESCRIPTION
				"Device 14 connection fail"
			::= { trapsTLP 40}	

		device15connFail			NOTIFICATION-TYPE
			STATUS      			current
			DESCRIPTION
				"Device 15 connection fail"
			::= { trapsTLP 41}	

		device16connFail			NOTIFICATION-TYPE
			STATUS      			current
			DESCRIPTION
				"Device 16 connection fail"
			::= { trapsTLP 42}	

		device17connFail			NOTIFICATION-TYPE
			STATUS      			current
			DESCRIPTION
				"Device 17 connection fail"
			::= { trapsTLP 43}

		device18connFail			NOTIFICATION-TYPE
			STATUS      			current
			DESCRIPTION
				"Device 18 connection fail"
			::= { trapsTLP 44}

		device19connFail			NOTIFICATION-TYPE
			STATUS      			current
			DESCRIPTION
				"Device 19 connection fail"
			::= { trapsTLP 45}

		device20connFail			NOTIFICATION-TYPE
			STATUS      			current
			DESCRIPTION
				"Device 20 connection fail"
			::= { trapsTLP 46}	

		device21connFail			NOTIFICATION-TYPE
			STATUS      			current
			DESCRIPTION
				"Device 21 connection fail"
			::= { trapsTLP 47}		

		device22connFail			NOTIFICATION-TYPE
			STATUS      			current
			DESCRIPTION
				"Device 22 connection fail"
			::= { trapsTLP 48}	

		device23connFail			NOTIFICATION-TYPE
			STATUS      			current
			DESCRIPTION
				"Device 23 connection fail"
			::= { trapsTLP 49}	
			
		device24connFail			NOTIFICATION-TYPE
			STATUS      			current
			DESCRIPTION
				"Device 24 connection fail"
			::= { trapsTLP 50}	
			
		device25connFail			NOTIFICATION-TYPE
			STATUS      			current
			DESCRIPTION
				"Device 25 connection fail"
			::= { trapsTLP 51}	

		device26connFail			NOTIFICATION-TYPE
			STATUS      			current
			DESCRIPTION
				"Device 26 connection fail"
			::= { trapsTLP 52}	
			
		device27connFail			NOTIFICATION-TYPE
			STATUS      			current
			DESCRIPTION
				"Device 27 connection fail"
			::= { trapsTLP 53}
			
		device28connFail			NOTIFICATION-TYPE
			STATUS      			current
			DESCRIPTION
				"Device 28 connection fail"
			::= { trapsTLP 54}
	
		device29connFail			NOTIFICATION-TYPE
			STATUS      			current
			DESCRIPTION
				"Device 29 connection fail"
			::= { trapsTLP 55}	

		device30connFail			NOTIFICATION-TYPE
			STATUS      			current
			DESCRIPTION
				"Device 30 connection fail"
			::= { trapsTLP 56}	

		device31connFail			NOTIFICATION-TYPE
			STATUS      			current
			DESCRIPTION
				"Device 31 connection fail"
			::= { trapsTLP 57}	

		device32connFail			NOTIFICATION-TYPE
			STATUS      			current
			DESCRIPTION
				"Device 32 connection fail"
			::= { trapsTLP 58}				
					
			
	-- Status/Config group 
		
		-- Inputs status group
		inputTeleport			OBJECT IDENTIFIER ::= { teleport 2}	
		
		inputStatusTableTLP OBJECT-TYPE
			SYNTAX     SEQUENCE OF InputStatusEntryTLP
			MAX-ACCESS not-accessible
			STATUS     current
			DESCRIPTION
					""
			::= { inputTeleport 1 }
			
		inputStatusEntryTLP OBJECT-TYPE
			SYNTAX     InputStatusEntryTLP
			MAX-ACCESS not-accessible
			STATUS     current
			DESCRIPTION
					"An entry (conceptual row) ."
			INDEX      { inputIndexTLP }
			::= { inputStatusTableTLP 1 }     
			
		InputStatusEntryTLP ::= SEQUENCE {
			inputIndexTLP    INTEGER,
			inputStateTLP    INTEGER
		} 
		
		inputIndexTLP OBJECT-TYPE
			SYNTAX     INTEGER
			MAX-ACCESS read-write
			STATUS     current
			DESCRIPTION
					"Input Number"
			::= { inputStatusEntryTLP 1 }
			
	
		inputStateTLP OBJECT-TYPE
			SYNTAX     INTEGER{ open(1), short(2) }
			MAX-ACCESS read-only
			STATUS     current
			DESCRIPTION
					"Input State"
			::= { inputStatusEntryTLP 2 }
		
		-- Output Status/Config Group   
    	outputTeleport		 OBJECT IDENTIFIER ::= { teleport 3}

		outputTeleportTable OBJECT-TYPE
			SYNTAX     SEQUENCE OF OutputTeleportEntry
			MAX-ACCESS not-accessible
			STATUS     current
			DESCRIPTION
					""
			::= { outputTeleport 1 }
			
		outputTeleportEntry OBJECT-TYPE
			SYNTAX     OutputTeleportEntry
			MAX-ACCESS not-accessible
			STATUS     current
			DESCRIPTION
					"An entry (conceptual row) in the outputTeleportTable."
			INDEX      { outIndex }
			::= { outputTeleportTable 1 }     
			
		OutputTeleportEntry ::= SEQUENCE {
			outIndex    INTEGER,
			outState    INTEGER
		} 

		
		outIndex OBJECT-TYPE
			SYNTAX     INTEGER
			MAX-ACCESS read-write
			STATUS     current
			DESCRIPTION
					"Index of Output"
			::= { outputTeleportEntry 1 }
			
		outState OBJECT-TYPE
			SYNTAX     INTEGER { open(1), short(2) }
			MAX-ACCESS read-write
			STATUS     current
			DESCRIPTION
					"State of Output"
			::= { outputTeleportEntry 2 }
		
		
		-- Firmware status group
		fwStatusTLP	OBJECT IDENTIFIER ::= { teleport 4}	
		
		fwVersionTLP OBJECT-TYPE
			SYNTAX     OCTET STRING
			MAX-ACCESS read-only
			STATUS     current
			DESCRIPTION
					"Firmware version"
			::= { fwStatusTLP 1 }
			
END
